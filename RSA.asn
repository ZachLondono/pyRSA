RSAKEY DEFINITIONS ::= BEGIN

    PUBLICKEY ::= SEQUENCE {
        n        INTEGER,
        e        INTEGER
    }
    
	PRIVATEKEY ::= SEQUENCE {
        p        INTEGER,
        q        INTEGER,
        d        INTEGER
    }

END
